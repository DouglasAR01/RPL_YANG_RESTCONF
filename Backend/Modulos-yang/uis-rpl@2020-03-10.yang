module uis-rpl {

  yang-version "1.1";

  // namespace
  namespace "urn:ietf:params:xml:ns:yang:uis-rpl";

  prefix "rpl";

  // import some basic types
  import ietf-routing {
    prefix "rt";
  }

  import ietf-yang-types {
    prefix "yang";
  }

  import ietf-interfaces {
    prefix "if";
  }

  import ietf-ip {
    prefix "ip";
  }

  import ietf-inet-types {
    prefix "inet";
  }


  // meta
  organization "Universidad Industrial de Santander";

  contact
    "Douglas Andrés Ramírez
     ra.douglas@hotmail.com";

  description
    "This module is an a first approach to an RPL
     (non-storing mode) YANG model for a root node.";

  revision 2020-03-10 {
    description
      "Global and interface statistics support.";
  }

  revision 2020-03-07 {
    description
      "Upward routing and downward routing support. (non-storing mode)";
  }

  revision 2020-02-27 {
    description
      "Support for multiple objective functions.";
  }
  revision 2019-10-15 {
    description
      "Initial revision.";
  }

  // feature statements
  feature dag-version-increment-timer {
    description
      "This feature indicates that the RPL implementation on the system
       supports DAG Version Increment Timers.";
  }

  feature global-statistics {
    description
      "This feature indicates that the system supports collecting
       global statistic data related to RPL.";
  }

  feature interface-statistics {
    description
      "This feature indicates that the system supports collecting
       per-interface statistic data related to RPL.";
  }

  // identity statements
  identity rpl {
    base rt:routing-protocol;
    description "Identity for the RPL routing protocol.";
  }

  identity objective-function {
    description
      "Base identity for objective functions.";
  }


  // typedef statements

  typedef of-ref {
    description
      "Reference to an objective function instance.";
    type leafref {
      path "/rt:routing/rt:control-plane-protocols/"
        + "rt:control-plane-protocol" +
        "/rpl:rpl/rpl:objective-functions/rpl:objective-function/rpl:name";
    }
  }

  typedef metric-ref {
    description
      "Reference to a metric type.";
    type leafref {
      path "/rt:routing/rt:control-plane-protocols/"
        + "rt:control-plane-protocol" +
        "/rpl:rpl/rpl:metrics/rpl:metric";
    }
  }


  // grouping statements

  grouping node-dodag-attributes {
    description
      "Grouping for route attributes.";

    leaf rank {
      type uint16 {
        range 1..max;
      }
      description
        "The current rank of the node in the DODAG.";
    }

    leaf cost {
      type decimal64 {
        fraction-digits 5;
        range 0..max;
      }
      description
        "The cost set up by the implemented metric.
         It could be distance to sink node, ETX, hops count, etc.";
    }
  }

  grouping trickle-timer {
    container trickle-timer {
      description
        "Trickle timer variables and parameters.";

      // PARAMETERS
      leaf i-min {
        description
          "The minimum interval size, Imin, is defined in milliseconds (ms).";
        type uint32 {
          range 1..max;
        }
        units 'milliseconds';
      }

      leaf i-max {
        description
          "The maximum interval size, Imax, is described as a number of
          doublings of the minimum interval size (the base-2 log(max/min)).";
        type uint8 {
          range 1..32;
        }
      }

      leaf k {
        description
          "The redundancy constant, k, is a natural number (an integer
            greater than zero).
            In RPL, when k has the value of 0, this is to be treated as
            a redundancy constant of infinity.";
        type uint8;
      }

      //VARIABLES
      leaf i {
        description
          "I, the current interval size.";
        type uint64;
        config false;
      }

      leaf t {
        description
          "t, a time within the current interval.";
        type uint64;
        config false;
      }

      leaf c {
        description
          "c, a counter.";
        type yang:counter32;
        config false;
      }
    }
  }

  grouping global-rpl-attributes {
    description
      "Global configuration and state attributes.";

    leaf dio-interval-min {
      type uint8 {
        range 0..32;
      }
      default 3;
      description
        "Number of doublings of the minimum DIO interval used to configure
         Imin for the DIO Trickle timer.
         By default has a value of 3. This configuration results in Imin of 8 ms.
         (Imin = 2^3 ms)";
    }

    leaf dio-interval-doublings {
      type uint8 {
        range 1..32;
      }
      default 20;
      description
        "Number of doublings of the maximum DIO interval used to configure
        Imax for the DIO Trickle timer.
        By default has a value of 20. This configuration results in Imax of 2.3 hours.
        (Imax = Imin * 2^20, Imin = 8ms)";
    }

    leaf dio-redundancy-constant {
      type uint8 {
        range 1..max;
      }
      default 10;
      description
        "Value used to configure k for the DIO Trickle timer.";
    }

    container dio-timer {
      description
       "DIO-timer information.";

      uses trickle-timer;

      leaf dio-timer {
        type uint64;
        description
          "A Trickle timer with variable interval in
           [0,2^DIOIntervalMin*2^DIOIntervalDoublings].";
        config false;
      }
    }//dio-timer container

    leaf dag-version-increment-timer {
      if-feature dag-version-increment-timer;
      config false;
      description
        "Up to one instance per DODAG of which the node is acting as DODAG root.
         May not be supported in all implementations.
         Expiry triggers increment of DODAGVersionNumber, causing a new series
         of updated DIO message to be sent.  Interval should be chosen
         appropriate to propagation time of DODAG and as appropriate to
         application requirements (e.g., response time versus overhead).";
      type uint32;
    }
  }

  // data definition statements

  // augment statements
  augment "/rt:routing/rt:control-plane-protocols/"
    + "rt:control-plane-protocol"{

      when "derived-from-or-self(rt:type, 'rpl:rpl')"{
        description
          "This augment is only valid for a routing protocol instance
          of RPL.";
      }

      description "RPL augmentation.";
      container rpl {
        description "RPL data.";

        uses global-rpl-attributes;

        container interfaces {
          description
            "Containing a list of RPL interfaces.";

          list interface {
            key "interface";
            description
              "List of RPL interfaces.";

            leaf interface {
              type if:interface-ref;
              description "Enable RPL on this interface.";
              // El must verifica que la interfaz a enlistar sea de una instancia RPL
              // Y que el protocolo IP sea la versión 6
              must "(derived-from-or-self("
                + "../../../../rt:type, 'rpl:rpl') and "
                + "/if:interfaces/if:interface[if:name=current()]/"
                + "ip:ipv6)" {
                error-message "Invalid interface type.";
                description
                  "RPL can only be enabled on IPv6 interfaces.";
              }
            }

            leaf channel-id {
              type uint8;
              description
                "Logical interface or channel ID.";
            }

            //Interface state data

            leaf oper-status {
              type enumeration {
                enum up {
                  description
                    "RPL is operational on this interface.";
                }
                enum down {
                  description
                    "RPL is not operational on this
                     interface.";
                }
              }
              config false;
              description
                "Operational state.";
            }

            container statistics {
              if-feature interface-statistics;
              config false;
              description
                "Interface statistic counters.";

              leaf bad-packets-rcvd {
                type yang:counter64;
                description
                  "The number of invalid RPL packets received.";
              }
              leaf packets-rcvd {
                type yang:counter64;
                description
                  "Total number of RPL packets received.";
              }
              leaf sent-packets {
                type yang:counter64;
                description
                  "Total number of RPL packets sent.";
              }
            }
          } //Interfaces list
        } //Interfaces container

        container objective-functions {
          description
           "Support for objective functions";

          list objective-function {
            key "type name";
            description
              "Each entry contains an objective function instance.";

            leaf type {
              type identityref {
                base objective-function;
              }
            }

            leaf name {
              type string;
              description
                "An arbitrary name of the objective function instance.";
            }

            leaf description {
              type string;
              description
                "Textual description of the objective function instance.";
            }
          }
        } //Fin contenedor de funciones objetivo

        container metrics {
          description
            "Metrics information container.";

          leaf-list metric {
            type string;
            min-elements 1;
            description "A list of metrics.";
          }
        }

        // Contenedor de direccionamiento
        container routing-modes {
          config false;
          description
           "IPv6 addressing and RPL routing information";

          //Posibles groupings de tabla de rutas, vecinos y padres elegidos
          container upward-routing {
            description
              "Neighbors, preferred parents, and dodag construction information.";

            container neighbors {
              description
                "IPv6 neighbor information.";

              list neighbor {
                key "ipv6-address";
                description
                  "A RPL neighbor.";

                leaf ipv6-address {
                  type inet:ipv6-address;
                  description
                    "IP address that a RPL neighbor is using as its
                     source address.";
                }

                leaf last-update {
                  type yang:date-and-time;
                  description
                    "The time when the most recent RPL update was
                     received from this neighbor.";
                }
                // Se podrían mostrar algunas otras estadísticas.
                uses node-dodag-attributes;
              }//Neighbor list
            } //Neighbors container

            container node-preferred-parents {
              description
                "Sub-dodag nodes preferred-parents information.";

              list node-preferred-parent {
                key "ipv6-address";
                description
                  "A node preferred-parent information.";

                leaf ipv6-address {
                  type inet:ipv6-address;
                  description
                    "IP address that the current node is using as its
                     source address.";
                }

                leaf parent-ipv6-address {
                  type inet:ipv6-address;
                  description
                    "IP address that the preferred-parent of the current node
                     is using as its source address.";
                }

                leaf parent-rank {
                  type uint16;
                  description
                    "The node preferred-parent rank. It could be 0 if
                    the current node rank is 1.";
                }

                leaf parent-cost {
                  type decimal64 {
                    fraction-digits 5;
                    range 0..max;
                  }
                  description
                    "The cost set up by the implemented metric at the
                     preferred-parent node.
                     It could be distance to sink node, ETX, hops count, etc.";
                }

                uses node-dodag-attributes;
              }//Preferred parents list
            }//Preferred parent container

            container dodag-topology {
              description
                "DODAG topology construction and mantaninment information.";

              leaf objective-function {
                type rpl:of-ref;
                description
                  "The OF used in the current RPL instance.
                   All DODAGs in the same RPL Instance use the same OF.
                   RFC6550 section 3.1.2.";
              }

              leaf metric {
                type rpl:metric-ref;
                description
                  "The metric used in the current RPL instance.";
              }

              leaf num-of-nodes {
                type uint16;
                description
                  "Number of nodes in the DODAG, including sink node.";
              }

              container dodag-version {
                description
                  "DODAG uniqueness identifier.";

                leaf rpl-instance-id {
                  type uint8;
                }

                leaf dodag-id {
                  type inet:ipv6-address;
                }

                leaf dodag-version-number {
                  type uint8;
                  description
                  "A DODAG is sometimes reconstructed from the DODAG root,
                   by incrementing the DODAGVersionNumber.";
                }
              }//Dodag-version container
            }//Dodag-topology container

          }//Upward routing container

          container downward-routing {
            config false;
            list routing-table {
              key "dest-ip";
              description
                "This list represents a routing table for RPL in non-storing MOP";

              leaf dest-ip {
                type inet:ipv6-address;
                description
                  "Destination IPv6 address.";
              }

              leaf next-hop-ip {
                type inet:ipv6-address;
                description
                  "Next hop IPv6 address.";
              }
            }//routing-table list
          }//downward-routing container
        }//routing-modes container

        container statistics {
          if-feature global-statistics;
          config false;
          description
            "Global statistic counters.";

          leaf received-daos {
            type yang:counter64;
            description
              "Count of received DAOs.";
          }
          leaf received-dios {
            type yang:counter64;
            description
              "Count of received DIOs.";
          }
          leaf received-dis {
            type yang:counter64;
            description
              "Count of received DISes.";
          }
          leaf sent-daos {
            type yang:counter64;
            description
              "Count of sent DAOs.";
          }
          leaf sent-dios {
            type yang:counter64;
            description
              "Count of sent DIOs.";
          }

        }

      }//Rpl container
    }//Augmentation container

  // rpc statements
  rpc get-route-stack {
    description
      "Returns (if exists) the full routing path to a node member of the DODAG.";

    input {
      leaf target-ipv6-address {
        type inet:ipv6-address;
        description
          "The Ipv6 address of the target node.";
      }
    }

    output {
      leaf-list route-stack {
        type inet:ipv6-address;
        description
         "A list of the IPv6 addresses which routes from the sink node to the
         target node. In order.";
        ordered-by "system";
      }
    }
  }

  // notification statements

}
